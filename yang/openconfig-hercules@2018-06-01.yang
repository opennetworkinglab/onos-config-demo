module openconfig-hercules {

  yang-version "1";

  // namespace
  namespace "http://openconfig.net/yang/hercules";

  prefix herc;

  import openconfig-extensions { prefix oc-ext; }

  // meta
  organization
    "OpenConfig Hercules Working Group";

  contact
    "openconfig-hercules@googlegroups.com";

  description
    "Defines OpenConfig extensions for the Hercules switch
    profile.";

  oc-ext:openconfig-version "0.2.0";

  revision 2018-06-01 {
    description
      "Initial version.";
    reference "0.2.0";
  }

  // data definition statements

  // Global container for Hercules-specific configuration and
  // operational state data.

  container hercules {
    description
      "Anchor container for data nodes defined by Hercules extensions.
      Each extension type should augment its data here.";

  }

}
